module netbeez-agent {

    yang-version "1";

    // namespace
    namespace "urn:srl_test/netbeez-agent";

    prefix "netbeez_agent";

    // import srl_nokia-common {
    //    prefix srl_nokia-comm;
    // }

    // Note that this module needs to be in the path for source-directories
    import srl_nokia-extensions {
      prefix srl_nokia-ext;
    }

    revision "2021-06-11" {
        description "Initial revision";
        reference "TBD";
    }

    grouping netbeez-agent-top {
        description "Top level grouping for Netbeez agent sample app";

        container netbeez-agent {
            presence "presence container";
            description "Top level enclosing container for netbeez-agent sample app
                         config and operational state data";

            leaf agent-key {
                description "NB_SECRET_KEY for agent to register with NetBeez";
                type string;
            }
        }
    }

    // data definition statements
    uses netbeez-agent-top;
}
